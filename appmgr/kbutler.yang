module kbutler {

    yang-version 1.1;

    // namespace
    namespace "urn:srl_ndk_apps/kbutler";

    prefix "srl_ndk_apps-kbutler";

    revision "2021-05-08" {
        description "Initial revision";
    }

    grouping kbutler-top {
        description "Top level grouping for Kubernetes Butler configuration and state";
        container kbutler {
            presence "Top-level container for the Kubernetes Butler configuration and state";
            description "Top level enclosing container for Kubernetes Butler";
            leaf controller {
                type string;
                description "Kubernetes API server this instance is connected to";
            }
            list service {
                key "service-name namespace";
                description "List of services being served by this device";
                leaf service-name {
                    type string;
                    description "Name of the service";
                }
                leaf namespace {
                    type string;
                    description "Name of the namespace this service is present in";
                }
                leaf oper-state {
                    type string;
                    description "Operational state of the service on this device";
                }
                leaf oper-reason {
                    type string;
                    description "Reason for the current operational state of the service";
                }
                list external-address {
                    key "address hostname";
                    description "List of external addresses this service can be reached via";
                    leaf address {
                        type string;
                        description "IP address this service can be reached via";
                    }
                    leaf hostname {
                        type string;
                        description "Hostname of a host providing the service";
                    }
                    leaf host-address {
                        type string;
                        description "IP address this host is advertising for service reachability";
                    }
                    leaf oper-state {
                        type string;
                        description "Operational state of reachability to the host+service";
                    }
                    leaf oper-reason {
                        type string;
                        description "Reason for the current operational state of the host+service";
                    }
                    leaf fib-programmed {
                        type boolean;
                        description "Indicates if this host+service is present in hardware, not just the routing table";
                    }
                }
            }
        }
    }

    uses kbutler-top;
}
